/******************************************************
* Copyright (C) 2023 isoftstone Technologies Co., Ltd. All rights reserved.
* Module description & tree structure
******************************************************/
module openEuler-sysctl.conf {
  namespace "urn:huawei:yang:openEuler-sysctl.conf";
  prefix "sysctl";

  organization
    "isoftstone";

  contact
    "Huawei Industrial Base
     Bantian, Longgang
     Shenzhen 518129
     People's Republic of China
     Website: http://www.huawei.com
     Email: support@huawei.com";

  description
    "This module contains a collection of YANG definitions for
     sysctl.conf config.
     The real path is : /etc/sysctl.conf";

  revision 2023-09-01 {
    description "Initial revision.";
    reference "";
  }

  // extension statements
  // feature statements
  // identity statements
  // typedef statements
  // grouping statements
  // data definition statements
  // augment statements
  // rpc statements
  // notification statements

  extension path{
    argument "filePath";
    description "The real path corresponding to the sysctl.conf file.";
  }

  extension type{
     argument "type";
     description "The type of this configuration file.";
  }

  extension spacer{
    argument "spacer";
    description "Spacer between configuration item and configuration value.";
  }

  container sysctl {

    description "the conf file in sysctl.conf modules.";

    container sysctl.conf {

      description "The file name is sysctl.conf";

      sysctl:path "openEuler:/etc/sysctl.conf";
      sysctl:type "kv";
      sysctl:spacer "=";
    }
  }
}
