/******************************************************
* Copyright (C) 2023 isoftstone Technologies Co., Ltd. All rights reserved.
* Module description & tree structure
******************************************************/
module openEuler-ntp.conf {
  namespace "urn:huawei:yang:openEuler-ntp.conf";
  prefix "ntp";

  organization
    "isoftstone";

  contact
    "Huawei Industrial Base
     Bantian, Longgang
     Shenzhen 518129
     People's Republic of China
     Website: http://www.huawei.com
     Email: support@huawei.com";

  description
    "This module contains a collection of YANG definitions for
     ntp config.
     The real path is : /etc/ntp.conf";

  revision 2023-07-10 {
    description "Initial revision.";
    reference "";
  }

  // extension statements
  // feature statements
  // identity statements
  // typedef statements
  // grouping statements
  // data definition statements
  // augment statements
  // rpc statements
  // notification statements

  extension path{
    argument "filePath";
    description "The real path corresponding to the ntp file.";
  }

  extension type{
     argument "type";
     description "The type of this configuration file.";
  }

  extension spacer{
    argument "spacer";
    description "Spacer between configuration item and configuration value.";
  }

  container ntp {

    description "the conf file in ntp modules.";

    container ntp.conf {

      description "The file name is ntp.conf";

      ntp:path "openEuler:/etc/ntp.conf";
      ntp:type "kv";
      ntp:spacer "";
    }
  }
}
