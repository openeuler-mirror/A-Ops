/******************************************************
* Copyright (C) 2023 isoftstone Technologies Co., Ltd. All rights reserved.
* Module description & tree structure
******************************************************/
module openEuler-bashrc {
  namespace "urn:huawei:yang:openEuler-bashrc";
  prefix "bashrc";

  organization
    "isoftstone";

  contact
    "Huawei Industrial Base
     Bantian, Longgang
     Shenzhen 518129
     People's Republic of China
     Website: http://www.huawei.com
     Email: support@huawei.com";

  description
    "This module contains a collection of YANG definitions for
     bashrc config.
     The real path is : /etc/bashrc";

  revision 2023-09-02 {
    description "Initial revision.";
    reference "";
  }

  // extension statements
  // feature statements
  // identity statements
  // typedef statements
  // grouping statements
  // data definition statements
  // augment statements
  // rpc statements
  // notification statements

  extension path{
    argument "filePath";
    description "The real path corresponding to the bashrc file.";
  }

  extension type{
     argument "type";
     description "The type of this configuration file.";
  }

  extension spacer{
    argument "spacer";
    description "Spacer between configuration item and configuration value.";
  }

  container bashrc {

    description "the conf file in bashrc modules.";

    container bashrc_config {

      description "The file name is bashrc_config";

      bashrc:path "openEuler:/etc/bashrc";
      bashrc:type "bash";
      bashrc:spacer "";
    }
  }
}
