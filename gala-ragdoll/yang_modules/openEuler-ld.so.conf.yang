/******************************************************
* Copyright (C) 2023 isoftstone Technologies Co., Ltd. All rights reserved.
* Module description & tree structure
******************************************************/
module openEuler-ld.so.conf {
  namespace "urn:huawei:yang:openEuler-ld.so.conf";
  prefix "ld";

  organization
    "isoftstone";

  contact
    "Huawei Industrial Base
     Bantian, Longgang
     Shenzhen 518129
     People's Republic of China
     Website: http://www.huawei.com
     Email: support@huawei.com";

  description
    "This module contains a collection of YANG definitions for
     ld.so config.
     The real path is : /etc/ld.so.conf";

  revision 2023-06-07 {
    description "Initial revision.";
    reference "";
  }

  // extension statements
  // feature statements
  // identity statements
  // typedef statements
  // grouping statements
  // data definition statements
  // augment statements
  // rpc statements
  // notification statements

  extension path{
    argument "filePath";
    description "The real path corresponding to the ld.so file.";
  }

  extension type{
     argument "type";
     description "The type of this configuration file.";
  }

  extension spacer{
    argument "spacer";
    description "Spacer between configuration item and configuration value.";
  }

  container ld {

    description "the conf file in ld.so modules.";

    container ld.so.conf {

      description "The file name is ld.so.conf";

      ld:path "openEuler:/etc/ld.so.conf";
      ld:type "kv";
      ld:spacer "";
    }
  }
}
