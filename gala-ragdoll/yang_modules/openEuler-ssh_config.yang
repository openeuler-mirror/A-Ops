/******************************************************
* Copyright (C) 2023 isoftstone Technologies Co., Ltd. All rights reserved.
* Module description & tree structure
******************************************************/
module openEuler-ssh_config {
  namespace "urn:huawei:yang:openEuler-ssh_config";
  prefix "ssh";

  organization
    "isoftstone";

  contact
    "Huawei Industrial Base
     Bantian, Longgang
     Shenzhen 518129
     People's Republic of China
     Website: http://www.huawei.com
     Email: support@huawei.com";

  description
    "This module contains a collection of YANG definitions for
     ssh_config.
     The real path is : /etc/ssh/ssh_config";

  revision 2023-07-10 {
    description "Initial revision.";
    reference "";
  }

  // extension statements
  // feature statements
  // identity statements
  // typedef statements
  // grouping statements
  // data definition statements
  // augment statements
  // rpc statements
  // notification statements

  extension path{
    argument "filePath";
    description "The real path corresponding to the repo file.";
  }

  extension type{
     argument "type";
     description "The type of this configuration file.";
  }

  extension spacer{
    argument "spacer";
    description "Spacer between configuration item and configuration value.";
  }

  container ssh {

    description "the conf file in ssh modules.";

    container ssh_config {

      description "The file name is ssh_config";

      ssh:path "openEuler:/etc/ssh/ssh_config";
      ssh:type "ssh";
      ssh:spacer "";
    }
  }
}
