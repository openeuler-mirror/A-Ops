/******************************************************
* Copyright (C) 2021 Huawei Technologies Co., Ltd. All rights reserved.
* Module description & tree structure
******************************************************/
module openEuler-logos-openEuler.repo {
  namespace "urn:huawei:yang:openEuler-logos-openEuler.repo";
  prefix "repo";

  organization
    "Huawei Technologies Co., Ltd.";

  contact
    "Huawei Industrial Base
     Bantian, Longgang
     Shenzhen 518129
     People's Republic of China
     Website: http://www.huawei.com
     Email: support@huawei.com";

  description
    "This module contains a collection of YANG definitions for
     yum repo.
     The real path is : /etc/yum.repos.d/openEuler.repo";

  revision 2021-05-13 {
    description "Initial revision.";
    reference "";
  }

  // extension statements
  // feature statements
  // identity statements
  // typedef statements
  // grouping statements
  // data definition statements
  // augment statements
  // rpc statements
  // notification statements

  extension path{
    argument "filePath";
    description "The real path corresponding to the repo file.";
  }

  extension type{
     argument "type";
     description "The type of this configuration file.";
  }

  extension spacer{
    argument "spacer";
    description "Spacer between configuration item and configuration value.";
  }

  container yum {

    description "the repo file in yum modules.";

    container openEuler.repo {

      description "The file name is openEuler.repo.";

      repo:path "openEuler:/etc/yum.repos.d/openEuler.repo";
      repo:type "ini";
      repo:spacer "=";

      list session {
        key "name";
        description "The first configuration item in repo, and the name of the configuration item is OS.";

        leaf name {
          type string;
          description "The name of the yum source of this session.";
        }

        leaf baseurl {
          type string;
          description "The remote address of the yum source of this OS.";
        }

        leaf enabled {
          type string;
          description "Whether the yum source of this OS is enabled.";
        }

        leaf gpgcheck {
          type string;
          description "Whether the gpgcheck of the yum source of this OS is enabled.";
        }

        leaf gpgkey {
          type string;
          description "If gpgcheck is enabled, gpgkey is the corresponding key address.";
        }
      }
    }
  }
  
}
