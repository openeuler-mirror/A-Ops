/******************************************************
* Copyright (C) 2023 isoftstone Technologies Co., Ltd. All rights reserved.
* Module description & tree structure
******************************************************/
module openEuler-resolv.conf {
  namespace "urn:huawei:yang:openEuler-resolv.conf";
  prefix "resolv";

  organization
    "isoftstone";

  contact
    "Huawei Industrial Base
     Bantian, Longgang
     Shenzhen 518129
     People's Republic of China
     Website: http://www.huawei.com
     Email: support@huawei.com";

  description
    "This module contains a collection of YANG definitions for
     sshd config.
     The real path is : /etc/resolv.conf";

  revision 2023-07-30 {
    description "Initial revision.";
    reference "";
  }

  // extension statements
  // feature statements
  // identity statements
  // typedef statements
  // grouping statements
  // data definition statements
  // augment statements
  // rpc statements
  // notification statements

  extension path{
    argument "filePath";
    description "The real path corresponding to the sshd file.";
  }

  extension type{
     argument "type";
     description "The type of this configuration file.";
  }

  extension spacer{
    argument "spacer";
    description "Spacer between configuration item and configuration value.";
  }

  container resolv {

    description "the conf file in resolv modules.";

    container resolv.conf {

      description "The file name is resolv.conf";

      resolv:path "openEuler:/etc/resolv.conf";
      resolv:type "resolv";
      resolv:spacer "";
    }
  }
}
