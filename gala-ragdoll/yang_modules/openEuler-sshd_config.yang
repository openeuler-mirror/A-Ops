/******************************************************
* Copyright (C) 2023 isoftstone Technologies Co., Ltd. All rights reserved.
* Module description & tree structure
******************************************************/
module openEuler-sshd_config {
  namespace "urn:huawei:yang:openEuler-sshd_config";
  prefix "sshd";

  organization
    "isoftstone";

  contact
    "Huawei Industrial Base
     Bantian, Longgang
     Shenzhen 518129
     People's Republic of China
     Website: http://www.huawei.com
     Email: support@huawei.com";

  description
    "This module contains a collection of YANG definitions for
     sshd config.
     The real path is : /etc/ssh/sshd_config";

  revision 2023-06-07 {
    description "Initial revision.";
    reference "";
  }

  // extension statements
  // feature statements
  // identity statements
  // typedef statements
  // grouping statements
  // data definition statements
  // augment statements
  // rpc statements
  // notification statements

  extension path{
    argument "filePath";
    description "The real path corresponding to the repo file.";
  }

  extension type{
     argument "type";
     description "The type of this configuration file.";
  }

  extension spacer{
    argument "spacer";
    description "Spacer between configuration item and configuration value.";
  }

  container ssh {

    description "the conf file in sshd modules.";

    container sshd_config {

      description "The file name is sshd_config";

      sshd:path "openEuler:/etc/ssh/sshd_config";
      sshd:type "sshd";
      sshd:spacer "";
    }
  }
}
