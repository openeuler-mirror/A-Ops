/******************************************************
* Copyright (C) 2023 isoftstone Technologies Co., Ltd. All rights reserved.
* Module description & tree structure
******************************************************/
module openEuler-rc.local {
  namespace "urn:huawei:yang:openEuler-rc.local";
  prefix "rc";

  organization
    "isoftstone";

  contact
    "Huawei Industrial Base
     Bantian, Longgang
     Shenzhen 518129
     People's Republic of China
     Website: http://www.huawei.com
     Email: support@huawei.com";

  description
    "This module contains a collection of YANG definitions for
     rc.local config.
     The real path is : /etc/rc.local";

  revision 2023-09-02 {
    description "Initial revision.";
    reference "";
  }

  // extension statements
  // feature statements
  // identity statements
  // typedef statements
  // grouping statements
  // data definition statements
  // augment statements
  // rpc statements
  // notification statements

  extension path{
    argument "filePath";
    description "The real path corresponding to the rc.local file.";
  }

  extension type{
     argument "type";
     description "The type of this configuration file.";
  }

  extension spacer{
    argument "spacer";
    description "Spacer between configuration item and configuration value.";
  }

  container rc {

    description "the conf file in rc modules.";

    container rc_config {

      description "The file name is rc.local_config";

      rc:path "openEuler:/etc/rc.local";
      rc:type "bash";
      rc:spacer "";
    }
  }
}
